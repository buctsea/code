module ietf-my {
  yang-version 1.1;
  namespace
    "urn:ietf:params:xml:ns:yang:ietf-my";
  prefix my;
  
  organization
    "IETF LSR - Link State Routing Working Group";
  contact
    "WG Web:   <https://datatracker.ietf.org/wg/lsr/>
     WG List:  <mailto:lsr@ietf.org>

     Author:   Haiyang Zhang
               <mailto:Haiyang@mail.com>

  description
    "This YANG module adds the support of configuring my device.

     This YANG module conforms to the Network Management
     Datastore Architecture (NMDA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";
  reference
    "RFC XXXX";

  revision 2025-08-28 {
    description
      "Initial version";
    reference
      "RFC XXXX: MY";
  }

  identity feeling {
    base uint32;
    description
      "My feeling is ---------------";
  }
}
